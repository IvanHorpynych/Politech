; File: WINDOWS.LSP  (C)	07/13/89	Soft Warehouse, Inc.


;		  * * *  muLISP Window Manager	* * *

(SETQ *PRODUCT* "muLISP")
(SETQ *CURRENT-WINDOW* 0)
(SETQ *WINDOWS* NIL)
(SETQ *SCREEN-ROWS* NIL)		; Number of rows on screen
(SETQ *SCREEN-COLS* NIL)		; Number of columns on screen
(SETQ *SCREEN-CLIP* 0)			; Screen bottom clip lines

(DEFUN WINDOWS (*COMMAND-LINE*
    *GCHOOK* *FREE-DATA*
    WINDOW PANE EXPN ROW1 COL1 ROW2 COL2 *CURRENT-AREA* *PROMPT*
    *OPTIONS* *INVERSE-OPTION* *MAX-LENGTH* *OPTION-COLUMN* *LOCAL-DEMONS*
    *UPDATE-FUNCTION* *AUTO-NEWLINE* *INTERRUPT-HOOK* *CURSOR-ON*)
  (SAVE-STATE)				; Save external state
  (INITIAL-ENTRY)			; Initial entry routine
  (CURSOR-OFF)				; Turn OFF cursor
  (CSMEMORY 940 0 T)			; Disable Ctrl-V insert mode toggle
  (CSMEMORY 962 6 T)			; Disable Ins insert mode toggle
  (MAKE-WINDOW NIL)			; Take whole window
  (SETQ *SCREEN-ROWS* (- (THIRD (MAKE-WINDOW)) *SCREEN-CLIP*)
	*SCREEN-COLS* (FOURTH (MAKE-WINDOW)))
  (SETQ *GCHOOK* 'GCHOOK)
  (GCHOOK)				; Initialize *FREE-DATA* for next GC
  (IF (NOT *WINDOWS*)
      (SETQ *WINDOWS* (LIST (LIST 0 (LIST NIL) 0 0
			      (- *SCREEN-ROWS* 5) *SCREEN-COLS*
			      (LIST *WORK-COLOR*) (LIST *WORK-BACKGROUND*)))) )
  (CLEAR-SCREEN)
  (BORDER-WINDOWS)
  (OPTION-WINDOW)
  (CLEAR-SCREEN)
  (STATUS-WINDOW)
  (CLEAR-SCREEN)
  (WINDOW-STATE *CURRENT-WINDOW* (APPLY *INIT-WINDOW* 'CREATE-WINDOW NIL))
  (SETQ *COMMAND-LINE* "")
  (UPDATE-WINDOWS)
  (SETQ *PROMPT* "")
  (LOOP
    (SETQ EXPN (CATCH NIL
	    (APPLY (CAR (WINDOW-STATE)) 'RUN-WINDOW (CDR (WINDOW-STATE))) ))

    ( ((EQ *THROW-TAG* 'CLOSE-WINDOW)			; Close window
	((NOT ((LAMBDA (*CURRENT-WINDOW*)
		(APPLY (CAR (WINDOW-STATE)) 'CLOSE-WINDOW (CDR (WINDOW-STATE))))
		  EXPN)))
	((CDR (WINDOW-STATES EXPN))			; Multi-layers?
	  (WINDOW-STATES EXPN
			 (DELETE-NTH (WINDOW-STATES EXPN) (WINDOW-PANE EXPN)))
	  (REPLACE-NTH (DELETE-NTH (NTH 6 (NTH EXPN *WINDOWS*))
				   (WINDOW-PANE EXPN))
		       (NTH EXPN *WINDOWS*)
		       6)
	  (REPLACE-NTH (DELETE-NTH (NTH 7 (NTH EXPN *WINDOWS*))
				   (WINDOW-PANE EXPN))
		       (NTH EXPN *WINDOWS*)
		       7)
	  (WINDOW-PANE EXPN (MIN (WINDOW-PANE EXPN)
				 (SUB1 (LENGTH (WINDOW-STATES EXPN)))))
	  (UPDATE-WINDOW EXPN) )
	(SETQ ROW1 (SUB1 (WINDOW-ROW EXPN))
	      COL1 (SUB1 (WINDOW-COL EXPN))
	      ROW2 (+ (WINDOW-ROW EXPN) (WINDOW-ROWS EXPN))
	      COL2 (+ (WINDOW-COL EXPN) (WINDOW-COLS EXPN))
	      *WINDOWS* (DELETE-NTH *WINDOWS* EXPN))
	( ((< *CURRENT-WINDOW* EXPN))
	  ((ZEROP *CURRENT-WINDOW*))
	  (SETQ *CURRENT-WINDOW* (SUB1 *CURRENT-WINDOW*)) )
	((= (LENGTH *WINDOWS*) 1)
	  (WINDOW-ROW 0 0)
	  (WINDOW-COL 0 0)
	  (WINDOW-ROWS 0 (- *SCREEN-ROWS* 5))
	  (WINDOW-COLS 0 *SCREEN-COLS*)
	  (UPDATE-WINDOW 0)
	  (BORDER-WINDOWS) )
	( ((AND (UPPER-RIGHT ROW1 COL1) (LOWER-RIGHT ROW2 COL1))
	    (LOOP
	      ((= ROW1 ROW2))
	      (SETQ EXPN (UPPER-RIGHT ROW1 COL1))
	      (WINDOW-COLS EXPN (- (+ (WINDOW-COLS EXPN) COL2) COL1))
	      (UPDATE-WINDOW EXPN)
	      (SETQ ROW1 (+ ROW1 (WINDOW-ROWS EXPN) 1)) ) )
	  ((AND (LOWER-LEFT ROW1 COL1) (LOWER-RIGHT ROW1 COL2))
	    (LOOP
	      ((= COL1 COL2))
	      (SETQ EXPN (LOWER-LEFT ROW1 COL1))
	      (WINDOW-ROWS EXPN (- (+ (WINDOW-ROWS EXPN) ROW2) ROW1))
	      (UPDATE-WINDOW EXPN)
	      (SETQ COL1 (+ COL1 (WINDOW-COLS EXPN) 1)) ) )
	  ((AND (UPPER-LEFT ROW1 COL2) (LOWER-LEFT ROW2 COL2))
	    (LOOP
	      ((= ROW1 ROW2))
	      (SETQ EXPN (UPPER-LEFT ROW1 COL2))
	      (WINDOW-COL EXPN (ADD1 COL1))
	      (WINDOW-COLS EXPN (- (+ (WINDOW-COLS EXPN) COL2) COL1))
	      (UPDATE-WINDOW EXPN)
	      (SETQ ROW1 (+ ROW1 (WINDOW-ROWS EXPN) 1)) ) )
	  ((AND (UPPER-LEFT ROW2 COL1) (UPPER-RIGHT ROW2 COL2))
	    (LOOP
	      ((= COL1 COL2))
	      (SETQ EXPN (UPPER-LEFT ROW2 COL1))
	      (WINDOW-ROW EXPN (ADD1 ROW1))
	      (WINDOW-ROWS EXPN (- (+ (WINDOW-ROWS EXPN) ROW2) ROW1))
	      (UPDATE-WINDOW EXPN)
	      (SETQ COL1 (+ COL1 (WINDOW-COLS EXPN) 1)) ) ) )
	(BORDER-WINDOWS) )

      ((EQ *THROW-TAG* 'SWITCH-PANE)			; Switch panes
	(WINDOW-PANE *CURRENT-WINDOW* EXPN)
	(UPDATE-WINDOW *CURRENT-WINDOW*) )

      ((EQ *THROW-TAG* 'SWITCH-WINDOW)			; Switch windows
	((= EXPN *CURRENT-WINDOW*))
	(MAKE-WINDOW NIL)
	(SET-CURSOR (SUB1 (WINDOW-ROW *CURRENT-WINDOW*))
		    (SUB1 (WINDOW-COL *CURRENT-WINDOW*)))
	(CHANGE-COLOR *FRAME-COLOR* *MENU-BACKGROUND*)
	(PRIN1 (ADD1 *CURRENT-WINDOW*))
	(SETQ *CURRENT-WINDOW* EXPN
	      *CURRENT-AREA*)
	(SET-CURSOR (SUB1 (WINDOW-ROW *CURRENT-WINDOW*))
		    (SUB1 (WINDOW-COL *CURRENT-WINDOW*)))
	(CHANGE-COLOR *MENU-BACKGROUND* *FRAME-COLOR* 0)
	(PRIN1 (ADD1 *CURRENT-WINDOW*)) )

      ((EQ *THROW-TAG* 'SPLIT-WINDOW)			; Split window
	(WINDOW-PANE (ADD1 *CURRENT-WINDOW*) 0)
	(WINDOW-STATES (ADD1 *CURRENT-WINDOW*)
		       (LIST (COPY-TREE (WINDOW-STATE))))
;If the above 3 lines of code are replaced with the next 2 lines, the new
;window will contain a copy of the hidden panes as well as the top pane.
;	(WINDOW-STATES (ADD1 *CURRENT-WINDOW*)
;		       (COPY-TREE (WINDOW-STATES)))
	(BORDER-WINDOWS)
	(UPDATE-WINDOW *CURRENT-WINDOW*)
	(UPDATE-WINDOW (ADD1 *CURRENT-WINDOW*)) )

      ((EQ *THROW-TAG* 'DESIGNATE-WINDOW)		; Designate window
	((APPLY (CAR (WINDOW-STATE)) 'CLOSE-WINDOW (CDR (WINDOW-STATE)))
	  (WINDOW-STATE *CURRENT-WINDOW* (APPLY EXPN 'CREATE-WINDOW NIL))
	  (UPDATE-WINDOW *CURRENT-WINDOW*) ) )

      ((EQ *THROW-TAG* 'OPEN-PANE)			; Open pane
	(WINDOW-STATES *CURRENT-WINDOW*
		(INSERT-NTH (APPLY EXPN 'CREATE-WINDOW NIL)
			    (WINDOW-STATES) (WINDOW-PANE)))
	(RPLACD (WORK-COLOR) (CONS (CAR (WORK-COLOR)) (CDR (WORK-COLOR))))
	(RPLACD (WORK-BACKGROUND) (CONS (CAR (WORK-BACKGROUND))
					(CDR (WORK-BACKGROUND))))
	(UPDATE-WINDOW *CURRENT-WINDOW*) )

      ((EQ *THROW-TAG* 'QUIT-PROGRAM)			; Quit program
	(SETQ WINDOW 0)
	(LOOP
	  ((= WINDOW (LENGTH *WINDOWS*))
	    ( ((RESTORE-STATE)) 		; Restore external video state
	      (MAKE-WINDOW (SUB1 *SCREEN-ROWS*) 0 1 *SCREEN-COLS*)
	      (CLEAR-SCREEN) )
	    (SYSTEM) )
	  (SETQ PANE 0)
	  ((LOOP
	    ((= PANE (LENGTH (WINDOW-STATES WINDOW))) NIL)
	    ((NOT (APPLY (CAR (NTH PANE (WINDOW-STATES WINDOW))) 'CLOSE-WINDOW
		     (CDR (NTH PANE (WINDOW-STATES WINDOW))))))
	    (INCQ PANE) ))
	  (INCQ WINDOW) ) )

      ((EQ *THROW-TAG* 'SWITCH-SCREEN)			; Switch screen
	(CURSOR-OFF)
	(MAKE-WINDOW NIL)
	( ((ZEROP (WINDOW-ROW 0))
	    (WINDOW-ROWS 0 (- (THIRD (MAKE-WINDOW)) 5 *SCREEN-CLIP*))
	    (WINDOW-COLS 0 (FOURTH (MAKE-WINDOW))) )
	  (SETQ ROW1 (/ (- *SCREEN-ROWS* 5) (- (THIRD (MAKE-WINDOW)) 5 *SCREEN-CLIP*))
		WINDOW (LENGTH *WINDOWS*))
	  (LOOP
	    ((ZEROP WINDOW))
	    (DECQ WINDOW)
	    (SETQ ROW2 (ROUND (+ (WINDOW-ROW WINDOW) (WINDOW-ROWS WINDOW)) ROW1))
	    (WINDOW-ROW WINDOW (ADD1 (ROUND (SUB1 (WINDOW-ROW WINDOW)) ROW1)))
	    (WINDOW-ROWS WINDOW (- ROW2 (WINDOW-ROW WINDOW))) )
	  (SETQ COL1 (/ (SUB1 *SCREEN-COLS*) (- (FOURTH (MAKE-WINDOW)) 1))
		WINDOW (LENGTH *WINDOWS*))
	  (LOOP
	    ((ZEROP WINDOW))
	    (DECQ WINDOW)
	    (SETQ COL2 (ROUND (+ (WINDOW-COL WINDOW) (WINDOW-COLS WINDOW)) COL1))
	    (WINDOW-COL WINDOW (ADD1 (ROUND (SUB1 (WINDOW-COL WINDOW)) COL1)))
	    (WINDOW-COLS WINDOW (- COL2 (WINDOW-COL WINDOW))) ) )
	(SETQ *SCREEN-ROWS* (- (THIRD (MAKE-WINDOW)) *SCREEN-CLIP*)
	      *SCREEN-COLS* (FOURTH (MAKE-WINDOW)))
	(BORDER-WINDOWS)
	(UPDATE-WINDOWS)
	(SETQ *PROMPT* ""
	      *OPTIONS*) )

      ((EQ *THROW-TAG* 'DRIVER))			; Throw to driver
      ((EQ *THROW-TAG* "Memory Full")			; Memory full error
	(ERROR-MESSAGE "Memory Full") )

      (THROW *THROW-TAG* EXPN) ) ) )			; Unrecognized throw

(DEFUN UPDATE-WINDOWS (
    WINDOW)
  (SETQ WINDOW 0)
  (LOOP
    ((= WINDOW (LENGTH *WINDOWS*)))
    (UPDATE-WINDOW WINDOW)
    (INCQ WINDOW) ) )

(DEFUN UPDATE-WINDOW (*CURRENT-WINDOW*)
  (APPLY (CAR (WINDOW-STATE)) 'UPDATE-WINDOW (CDR (WINDOW-STATE))) )

(DEFUN QUIT-PROGRAM ()
  (THROW 'QUIT-PROGRAM) )

;		* * *	Window Option Functions   * * *

(DEFUN CHANGE-WINDOW ()
  (EXECUTE-OPTION 'WINDOW '(
	("Close" . CLOSE-WINDOW)
	("Designate" . DESIGNATE-WINDOW)
	("Flip" . NEXT-PANE)
	("Goto" . GOTO-WINDOW)
	("Next" . NEXT-WINDOW)
	("Open" . OPEN-PANE)
	("Previous" . LAST-WINDOW)
	("Split" "WINDOW SPLIT" (
		("Horizontal" . HORIZONTAL-SPLIT)
		("Vertical" . VERTICAL-SPLIT) )) )) )

(DEFUN CLOSE-WINDOW (
    WINDOW)
  ((OR (CDR *WINDOWS*) (CDR (WINDOW-STATES)))
    (RPLACA (CAR CLOSE-WINDOW) (ADD1 *CURRENT-WINDOW*))
    (LOOP
      ((NOT (MODE-QUERY "WINDOW CLOSE" CLOSE-WINDOW)) NIL)
      (SETQ WINDOW (PARSE-INTEGER-CAR (CAR CLOSE-WINDOW)))
      ((AND WINDOW (<= 1 WINDOW (LENGTH *WINDOWS*)))
	(THROW 'CLOSE-WINDOW (SUB1 WINDOW)) )
      (ERROR-BEEP) ) ) )

(SETQ CLOSE-WINDOW '(("" "Enter window number" "Window" 4)))

(DEFUN OPEN-PANE ()
  (RPLACA (CAR DESIGNATE-WINDOW) (CAR (WINDOW-STATE)))
  (REPLACE-NTH *WINDOW-TYPES* (CAR DESIGNATE-WINDOW) 3)
  ((MODE-QUERY "WINDOW OPEN" DESIGNATE-WINDOW)
    (THROW 'OPEN-PANE (CAAR DESIGNATE-WINDOW)) ) )

(DEFUN DESIGNATE-WINDOW ()
  (RPLACA (CAR DESIGNATE-WINDOW) (CAR (WINDOW-STATE)))
  (REPLACE-NTH *WINDOW-TYPES* (CAR DESIGNATE-WINDOW) 3)
  ((MODE-QUERY "WINDOW DESIGNATE" DESIGNATE-WINDOW)
    (THROW 'DESIGNATE-WINDOW (CAAR DESIGNATE-WINDOW)) ) )

(SETQ DESIGNATE-WINDOW '(("" "Enter window type" "Type" NIL)))
(IF (ATOM *WINDOW-TYPES*) (SETQ *WINDOW-TYPES*))

(DEFUN GOTO-WINDOW (
    WINDOW)
  (RPLACA (CAR GOTO-WINDOW)
	  (ADD1 (MOD (ADD1 *CURRENT-WINDOW*) (LENGTH *WINDOWS*))))
  (LOOP
    ((NOT (MODE-QUERY "WINDOW GOTO" GOTO-WINDOW)) NIL)
    (SETQ WINDOW (PARSE-INTEGER-CAR (CAR GOTO-WINDOW)))
    ((AND WINDOW (<= 1 WINDOW (LENGTH *WINDOWS*)))
      (THROW 'SWITCH-WINDOW (SUB1 WINDOW)) )
    (ERROR-BEEP) ) )

(SETQ GOTO-WINDOW '(("" "Enter window number" "Window" 4)))

(DEFUN LAST-WINDOW ()
  (THROW 'SWITCH-WINDOW (MOD (SUB1 *CURRENT-WINDOW*) (LENGTH *WINDOWS*))) )

(DEFUN NEXT-WINDOW ()
  (THROW 'SWITCH-WINDOW (MOD (ADD1 *CURRENT-WINDOW*) (LENGTH *WINDOWS*))) )

(DEFUN LAST-PANE ()
  (THROW 'SWITCH-PANE (MOD (SUB1 (WINDOW-PANE)) (LENGTH (WINDOW-STATES)))) )

(DEFUN NEXT-PANE ()
  (THROW 'SWITCH-PANE (MOD (ADD1 (WINDOW-PANE)) (LENGTH (WINDOW-STATES)))) )

(DEFUN HORIZONTAL-SPLIT (
    ROW)
  (RPLACA (CAR HORIZONTAL-SPLIT) (CEILING (WINDOW-ROWS) 2))
  (LOOP
    ((NOT (MODE-QUERY "WINDOW SPLIT HORIZONTAL" HORIZONTAL-SPLIT)) NIL)
    (SETQ ROW (PARSE-INTEGER-CAR (CAR HORIZONTAL-SPLIT)))
    ((AND ROW (<= 3 ROW (- (WINDOW-ROWS) 2)))
      (CURRENT-WINDOW T)
      (RESTORE-BORDER)
      (INSERT-STATE)
      (WINDOW-ROWS *CURRENT-WINDOW* (SUB1 ROW))
      (WINDOW-ROW (ADD1 *CURRENT-WINDOW*)
		  (+ (WINDOW-ROW (ADD1 *CURRENT-WINDOW*)) ROW))
      (WINDOW-ROWS (ADD1 *CURRENT-WINDOW*)
		   (- (WINDOW-ROWS (ADD1 *CURRENT-WINDOW*)) ROW))
      (THROW 'SPLIT-WINDOW) )
    (ERROR-BEEP) ) )

(SETQ HORIZONTAL-SPLIT '(("" "Enter line number" "At line" 4)))

(DEFUN VERTICAL-SPLIT (
    COL)
  (RPLACA (CAR VERTICAL-SPLIT) (CEILING (WINDOW-COLS) 2))
  (LOOP
    ((NOT (MODE-QUERY "WINDOW SPLIT VERTICAL" VERTICAL-SPLIT)) NIL)
    (SETQ COL (PARSE-INTEGER-CAR (CAR VERTICAL-SPLIT)))
    ((AND COL (<= 7 COL (- (WINDOW-COLS) 6)))
      (CURRENT-WINDOW T)
      ( ((MEDIUM-RESOLUTION-P))
	((EVENP COL))
	(DECQ COL) )
      (RESTORE-BORDER)
      (INSERT-STATE)
      (WINDOW-COLS *CURRENT-WINDOW* (SUB1 COL))
      (WINDOW-COL (ADD1 *CURRENT-WINDOW*)
		  (+ (WINDOW-COL (ADD1 *CURRENT-WINDOW*)) COL))
      (WINDOW-COLS (ADD1 *CURRENT-WINDOW*)
		   (- (WINDOW-COLS (ADD1 *CURRENT-WINDOW*)) COL))
      (THROW 'SPLIT-WINDOW) )
    (ERROR-BEEP) ) )

(SETQ VERTICAL-SPLIT '(("" "Enter column number" "At column" 4)))

(DEFUN INSERT-STATE (
    LST1 LST2)
  (SETQ LST1 (NTHCDR *CURRENT-WINDOW* *WINDOWS*)
	LST2 (CAR LST1)
	LST2 (NCONC (BUTLAST LST2 2) (LIST (COPY-LIST (SEVENTH LST2))
					   (COPY-LIST (EIGHTH LST2)))))
  (RPLACD LST1 (CONS LST2 (CDR LST1))) )

(DEFUN UPPER-LEFT (ROW COL
    WINDOW)
  (SETQ WINDOW 0)
  (LOOP
    ((= WINDOW (LENGTH *WINDOWS*)) NIL)
    ((AND (= ROW (SUB1 (WINDOW-ROW WINDOW)))
	  (= COL (SUB1 (WINDOW-COL WINDOW)))) WINDOW)
    (INCQ WINDOW) ) )

(DEFUN UPPER-RIGHT (ROW COL
    WINDOW)
  (SETQ WINDOW 0)
  (LOOP
    ((= WINDOW (LENGTH *WINDOWS*)) NIL)
    ((AND (= ROW (SUB1 (WINDOW-ROW WINDOW)))
	  (= COL (+ (WINDOW-COL WINDOW) (WINDOW-COLS WINDOW)))) WINDOW)
    (INCQ WINDOW) ) )

(DEFUN LOWER-LEFT (ROW COL
    WINDOW)
  (SETQ WINDOW 0)
  (LOOP
    ((= WINDOW (LENGTH *WINDOWS*)) NIL)
    ((AND (= ROW (+ (WINDOW-ROW WINDOW) (WINDOW-ROWS WINDOW)))
	  (= COL (SUB1 (WINDOW-COL WINDOW)))) WINDOW)
    (INCQ WINDOW) ) )

(DEFUN LOWER-RIGHT (ROW COL
    WINDOW)
  (SETQ WINDOW 0)
  (LOOP
    ((= WINDOW (LENGTH *WINDOWS*)) NIL)
    ((AND (= ROW (+ (WINDOW-ROW WINDOW) (WINDOW-ROWS WINDOW)))
	  (= COL (+ (WINDOW-COL WINDOW) (WINDOW-COLS WINDOW)))) WINDOW)
    (INCQ WINDOW) ) )

;		* * *	Window State Functions	 * * *

(DEFUN UPDATE-STATE (LST1
    LST2)
  (SETQ LST2 (WINDOW-STATE))
  (LOOP
    (POP LST2)
    ((NULL LST2))
    (RPLACA LST2 (EVAL (POP LST1))) ) )

(DEFUN WINDOW-PANE LST
  (WINDOW-BOX 0) )

(DEFUN WINDOW-STATES LST
  (WINDOW-BOX 1) )

(DEFUN WINDOW-STATE LST
  ((NULL LST)
    (NTH (WINDOW-PANE) (WINDOW-STATES)) )
  ((CDR LST)
    (REPLACE-NTH (CADR LST) (WINDOW-STATES (CAR LST)) (WINDOW-PANE (CAR LST)))
    (CADR LST) )
  (NTH (WINDOW-PANE (CAR LST)) (WINDOW-STATES (CAR LST))) )

(DEFUN WINDOW-ROW LST
  (WINDOW-BOX 2) )

(DEFUN WINDOW-COL LST
  (WINDOW-BOX 3) )

(DEFUN WINDOW-ROWS LST
  (WINDOW-BOX 4) )

(DEFUN WINDOW-COLS LST
  (WINDOW-BOX 5) )

(DEFUN WINDOW-BOX (NUM)
  ((NULL LST)
    (NTH NUM (NTH *CURRENT-WINDOW* *WINDOWS*)) )
  ((CDR LST)
    (REPLACE-NTH (CADR LST) (NTH (CAR LST) *WINDOWS*) NUM)
    (CADR LST) )
  (NTH NUM (NTH (CAR LST) *WINDOWS*)) )

;		* * *	Work Screen Color Selection   * * *

(DEFUN WORK-COLOR ()
  (NTHCDR (WINDOW-PANE) (NTH 6 (NTH *CURRENT-WINDOW* *WINDOWS*))) )

(DEFUN WORK-BACKGROUND ()
  (NTHCDR (WINDOW-PANE) (NTH 7 (NTH *CURRENT-WINDOW* *WINDOWS*))) )


(SETQ *WORK-COLOR* 15)
(SETQ *WORK-BACKGROUND* 0)

(DEFUN SET-WORK-COLOR (
    LST)
  ((SETQ LST (SET-COLOR 'WORK
			(LIST (CAR (WORK-COLOR)) (CAR (WORK-BACKGROUND)))
			'("Foreground" "Background")))
    (RPLACA (WORK-COLOR) (FIRST LST))
    (RPLACA (WORK-BACKGROUND) (SECOND LST))
    (THROW 'SWITCH-PANE (WINDOW-PANE)) ) )

(SETQ *FRAME-COLOR* 3)
(SETQ *OPTION-COLOR* 7)
(SETQ *PROMPT-COLOR* 13)
(SETQ *STATUS-COLOR* 11)
(SETQ *MENU-BACKGROUND* 0)
(SETQ *BORDER-COLOR* NIL)

(DEFUN SET-MENU-COLOR (
    LST)
  ((SETQ LST (SET-COLOR 'MENU
			(LIST *FRAME-COLOR* *OPTION-COLOR*
			    *PROMPT-COLOR* *STATUS-COLOR* *MENU-BACKGROUND*
			    (OR *BORDER-COLOR* (BORDER-COLOR) 0))
			'("Frame" "Option" "Prompt" "Status" "Background"
			    "Border")))
    (SETQ *FRAME-COLOR* (FIRST LST)
	  *OPTION-COLOR* (SECOND LST)
	  *PROMPT-COLOR* (THIRD LST)
	  *STATUS-COLOR* (FOURTH LST)
	  *MENU-BACKGROUND* (FIFTH LST))
    (SET-VIDEO-MODE *VIDEO-MODE* (SIXTH LST))
    (THROW 'SWITCH-SCREEN) ) )


(DEFUN SET-COLOR (TITLE LST1 LST2
; Query user for colors and returns a list of color numbers, else NIL.
; LST1 is the current colors and LST2 is the field names.
    NUM)
  (PROMPT-WINDOW)
  (IF (NOT (MEDIUM-RESOLUTION-P))
      (WRITE-STRING "Enter color number:") )
  (SETQ NUM 0)
  (LOOP 				; Display 16 numbers in color
    ((= NUM 16))
    (CHANGE-COLOR *PROMPT-COLOR* *MENU-BACKGROUND*)
    (SPACES 1)
    (CHANGE-COLOR NUM *MENU-BACKGROUND*)
    (PRIN1 NUM)
    (INCQ NUM) )
  (SETQ LST1 (MAPCAR '(LAMBDA (NUM STRING) (LIST NUM "" STRING 3)) LST1 LST2)
	*PROMPT* "")
  (LOOP 				; Query for new color numbers
    ((NOT (MODE-QUERY (PACK* 'COLOR " " TITLE) LST1))  NIL)
    (SETQ LST2 (MAPCAR 'PARSE-INTEGER-CAR LST1))
    ((EVERY 'COLORP LST2)  LST2)
    (ERROR-BEEP) ) )

(DEFUN COLORP (NUM)
  (AND NUM (>= NUM 0)) )

;		* * *	Video Mode Selection   * * *

(SETQ *VIDEO-MODE* NIL)
(SETQ *LAST-VIDEO-MODE* NIL)

(DEFUN SET-DISPLAY (
    MODE)
  ((SETQ MODE (VIDEO-MODE))
    ((= MODE 255) NIL)
    (RPLACA (FIRST SET-DISPLAY)
	    (IF (GRAPHICS-MODE-P) "Graphics" "Text") )
    (RPLACA (SECOND SET-DISPLAY)
	    (IF (OR (MEDIUM-RESOLUTION-P) (= MODE 65)) "Medium" "High") )
    (RPLACA (THIRD SET-DISPLAY)
	    (PROGN ((<= MODE 3)
		     ((EQ (CAR (THIRD SET-DISPLAY)) "") "CGA")
		     (CAR (THIRD SET-DISPLAY)) )
		   ((<= MODE 6) 	"CGA")
		   ((= MODE 7)
		     ((EQ (CAR (THIRD SET-DISPLAY)) "") "MDA")
		     (CAR (THIRD SET-DISPLAY)) )
		   ((<= MODE 10)	"PCjr")
		   ((<= 64 MODE 66)	"AT&T")
		   ((<= 126 MODE 127)	"Hercules")
		   ((<= 13 MODE 16)	"EGA")
		   ((= MODE 17) 	"MCGA")
		   "VGA" ))
    ((MODE-QUERY 'DISPLAY SET-DISPLAY)
      ( ((EQ (FIRST (FIRST SET-DISPLAY)) "Text")
	  (SETQ MODE (IF (OR (EQ (FIRST (THIRD SET-DISPLAY)) "MDA")
			     (EQ (FIRST (THIRD SET-DISPLAY)) "Hercules"))
			 7
			 (IF (EQ (FIRST (SECOND SET-DISPLAY)) "High") 3 1))) )
	((EQ (FIRST (THIRD SET-DISPLAY)) "CGA")
	  (SETQ MODE (IF (EQ (FIRST (SECOND SET-DISPLAY)) "High") 6 4)) )
	((EQ (FIRST (THIRD SET-DISPLAY)) "PCjr")
	  (SETQ MODE (IF (EQ (FIRST (SECOND SET-DISPLAY)) "High") 10 9)) )
	((EQ (FIRST (THIRD SET-DISPLAY)) "AT&T")
	  (SETQ MODE (IF (EQ (FIRST (SECOND SET-DISPLAY)) "High") 64 4)) )
	((EQ (FIRST (THIRD SET-DISPLAY)) "Hercules")
	  (SETQ MODE 126) )
	((EQ (FIRST (THIRD SET-DISPLAY)) "MCGA")
	  (SETQ MODE 17) )
	((EQ (FIRST (THIRD SET-DISPLAY)) "VGA")
	  (SETQ MODE 18) )
	(RPLACA (CAR EGA-DISPLAY)
		(PROGN ((<= MODE 3) (CAAR EGA-DISPLAY))
		       ((OR (= MODE 7) (= MODE 15))  "Monochrome")
		       ((<= 16 MODE 18) 	     "Enhanced")
		       "Color"))
	((MODE-QUERY "DISPLAY MONITOR" EGA-DISPLAY)
	  ((EQ (CAAR EGA-DISPLAY) "Monochrome")
	    (SETQ MODE 15) )
	  ((EQ (FIRST (SECOND SET-DISPLAY)) "High")
	    ((EQ (CAAR EGA-DISPLAY) "Enhanced")
	      (SETQ MODE 16) )
	    (SETQ MODE 14) )
	  (SETQ MODE 13) )
	(RETURN) )
      (IF (NEQL MODE (VIDEO-MODE))
	  (SETQ *LAST-VIDEO-MODE* (VIDEO-MODE)) )
      (SET-VIDEO-MODE MODE *BORDER-COLOR*)
      (THROW 'SWITCH-SCREEN) ) ) )

(SETQ SET-DISPLAY '(
  ("" "Select screen mode" "Mode" ("Text" "Graphics"))
  ("" "Select screen resolution" "Resolution" ("Medium" "High"))
  ("" "Select display adapter" "Adapter"
		("MDA" "CGA" "EGA" "MCGA" "VGA" "Hercules" "AT&T" "PCjr")) ))

(SETQ EGA-DISPLAY '(
  ("Color" "Select monitor type" "Monitor" ("Color" "Enhanced" "Monochrome")) ))


(DEFUN SET-VIDEO-MODE (VIDEO-MODE BORDER-COLOR FLAG)
; Sets video mode and border color and updates *VIDEO-MODE* and *BORDER-COLOR*.
; If FLAG is nonNIL and already in desired video mode, the screen is not
; cleared and SET-VIDEO-MODE returns NIL.
  (MAKE-WINDOW NIL)					; Full screen
  (CURSOR-LINES NIL)					; Normal cursor lines
  (BORDER-COLOR 0)
  ( ((AND FLAG (EQL VIDEO-MODE (VIDEO-MODE))))
    (VIDEO-MODE VIDEO-MODE)
    (SETQ FLAG) )
  ( ((GRAPHICS-MODE-P))
    (BORDER-COLOR BORDER-COLOR) )
  (SETQ *VIDEO-MODE* VIDEO-MODE
	*BORDER-COLOR* BORDER-COLOR)
  (NOT FLAG) )

(DEFUN GRAPHICS-MODE-P (
    MODE)
  (AND (SETQ MODE (VIDEO-MODE)) (>= MODE 4) (/= MODE 7)) )

(DEFUN MEDIUM-RESOLUTION-P (
    MODE)
  (SETQ MODE (VIDEO-MODE))
  (MEMBER MODE '(0 1 4 5 9 13 19)) )

;		* * *	Line Editor Entry Mode	 * * *

(DEFUN SET-INSERT ()
  (RPLACA (CAR SET-INSERT) (IF *INSERT-MODE* "Insert" "Overwrite"))
  ((MODE-QUERY 'MODE SET-INSERT)
    (INSERT-STATUS (EQ (CAAR SET-INSERT) "Insert")) ) )

(SETQ SET-INSERT '(("" "Select edit mode" "Edit" ("Insert" "Overwrite"))))

(DEFUN TOGGLE-INSERT ()
  (INSERT-STATUS (NOT *INSERT-MODE*)) )

(SETQ *SHOW-INSERT* T)		; Insert status is displayed iff nonNIL.

(DEFUN INSERT-STATUS (MODE)
  (SETQ *INSERT-MODE* MODE)
  ((NOT *SHOW-INSERT*))
  (STATUS-WINDOW)
  (SET-CURSOR 0 (TRUNCATE (* 2 *SCREEN-COLS*) 3))
  ((NOT *INSERT-MODE*)
    (SPACES 6) )
  (WRITE-STRING "Insert") )


(SETQ *MUTE* "No")

(DEFUN SET-MUTE ()
  (RPLACA (CAR SET-MUTE) *MUTE*)
  ((MODE-QUERY 'MUTE SET-MUTE)
    (SETQ *MUTE* (CAAR SET-MUTE)) ) )

(SETQ SET-MUTE '(("" "Mute warning messages" "Active" ("Yes" "No"))))


;		* * *	Execute DOS command   * * *

(DEFUN GO-DOS (
    COMMAND )
  (SETQ COMMAND (PROMPT-INPUT "Enter DOS command"
		    (PACK* (DEFAULT-DRIVE) ":\\" (DEFAULT-PATH) "> ") ""))
  ((EQ *LINE-TERMINATOR* 27)  NIL)
  ((PROBE-FILE (GETSET 'COMSPEC))
    (SHOW-PROMPT "")
    ( ((RESTORE-STATE)) 			; Restore external video state
      (MAKE-WINDOW (- *SCREEN-ROWS* 3) 0 3 *SCREEN-COLS*)
      (CLEAR-SCREEN)
      (MAKE-WINDOW NIL)
      (SET-CURSOR (- *SCREEN-ROWS* 3) 0) )
    ( ((EQ COMMAND "")
	(WRITE-LINE (PACK* "Type  EXIT	to return to " *PRODUCT*))
	(EXECUTE (GETSET 'COMSPEC) "") )
      (EXECUTE (GETSET 'COMSPEC) (PACK* "/C " COMMAND))
      (TERPRI)
      (WRITE-STRING "Press any key to continue")
      (CLEAR-INPUT T)
      (LOOP
	((NEQ (READ-CONSOLE-BYTE) 19)) ) )
    (SAVE-STATE)				; Save external video state
    (SET-VIDEO-MODE *VIDEO-MODE* *BORDER-COLOR* T)
    (THROW 'SWITCH-SCREEN) )
  (ERROR-MESSAGE "Cannot find COMMAND.COM") )

(SETQ *EDIT-TERMINATORS* '(27 13 10))
(SETQ *OPTION-DELAY* 0)

(DEFUN EXECUTE-OPTION (TITLE OPTIONS
    NUM CHAR POSITION)
  (LOOP
    (SETQ NUM 0)
    (LOOP
      (LOOP
	( ((LISTEN))
	  (SHOW-INVERSE-OPTION TITLE OPTIONS NUM) )
	((SETQ CHAR (READ-CONSOLE-STATUS)))
	(SHOW-PROMPT "Enter option")
	(PROMPT-WINDOW) )
      ((MEMBER CHAR *EDIT-TERMINATORS*))
      ((OR (SETQ POSITION (POSITION (CHAR-UPCASE (ASCII CHAR)) OPTIONS
		    '(LAMBDA (CHAR OPTION) (CHAR= CHAR (CAR OPTION)))))
	   (AND (ALPHA-CHAR-P (ASCII CHAR))
		(SETQ POSITION (POSITION (CHAR-UPCASE (ASCII CHAR)) OPTIONS
		    '(LAMBDA (CHAR OPTION) (FINDSTRING CHAR (CAR OPTION)))))))
	(SETQ NUM POSITION)
	((ZEROP *OPTION-DELAY*))
	(SHOW-INVERSE-OPTION TITLE OPTIONS NUM)
	(TONE NIL *OPTION-DELAY*) )
      ( ((OR (= CHAR 32) (= CHAR 9))
	  (SETQ NUM (MOD (ADD1 NUM) (LENGTH OPTIONS))) )
	((OR (= CHAR 8) (= CHAR 2) (= CHAR -15))
	  (SETQ NUM (MOD (SUB1 NUM) (LENGTH OPTIONS))) )
	(ERROR-BEEP) ) )
    ((= CHAR 27) NIL)
    ( ((EQ OPTIONS *OPTIONS*)
	(OPTION-WINDOW)
	(SHOW-OPTION *INVERSE-OPTION* OPTIONS)
	(SETQ *OPTIONS* OPTIONS) ) )
    (SETQ *INVERSE-OPTION* NIL
	  CHAR (CDR (NTH NUM OPTIONS)))
    ((IF (ATOM CHAR)
	 (FUNCALL CHAR (CAR (NTH NUM OPTIONS)))
	 (APPLY 'EXECUTE-OPTION CHAR))) ) )

(DEFUN SHOW-INVERSE-OPTION (TITLE OPTIONS NUM)
  (SHOW-OPTIONS TITLE OPTIONS)
  ((EQ NUM *INVERSE-OPTION*))
  (OPTION-WINDOW)
  (SHOW-OPTION *INVERSE-OPTION* OPTIONS)
  (SETQ *INVERSE-OPTION* NUM
	*OPTIONS* OPTIONS)
  (CHANGE-COLOR *MENU-BACKGROUND* *OPTION-COLOR* 0)
  (SHOW-OPTION *INVERSE-OPTION* OPTIONS)
  (CHANGE-COLOR *OPTION-COLOR* *MENU-BACKGROUND*) )

(DEFUN SHOW-OPTIONS (TITLE OPTIONS)
  ((EQ OPTIONS *OPTIONS*))
  (OPTION-WINDOW)
  (CLEAR-SCREEN)
  (WRITE-STRING TITLE)
  (WRITE-STRING ": ")
  (SETQ *OPTIONS* OPTIONS
	*OPTION-COLUMN* (COLUMN)
	*MAX-LENGTH* (MAX-LENGTH OPTIONS)
	*INVERSE-OPTION*)
  (LOOP
    (LOOP
      (WRITE-STRING (SUBSTRING (CAAR OPTIONS) 0 (SUB1 *MAX-LENGTH*)))
      (POP OPTIONS)
      ((ATOM OPTIONS))
      ((>= (+ (COLUMN) (MIN *MAX-LENGTH* (LENGTH (CAAR OPTIONS))))
	   *SCREEN-COLS*))
      (SPACES 1) )
    ((ATOM OPTIONS))
    (TERPRI)
    (SPACES *OPTION-COLUMN*) ) )

(DEFUN MAX-LENGTH (OPTIONS
    ROW COL MAX LST)
  (SETQ MAX (REDUCE '(LAMBDA (NUM OPTION)
	      (MAX NUM (LENGTH (CAR OPTION))) ) OPTIONS 0))
  (LOOP
    (SETQ LST OPTIONS
	  ROW 0)
    ((LOOP
	((= ROW (IF (SMALL-SCREENP) 3 2)) NIL)
	(SETQ COL *OPTION-COLUMN*)
	(LOOP
	  ((ATOM LST)
	    (RETURN MAX) )
	  (SETQ COL (+ COL (MIN MAX (LENGTH (CAAR LST))) 1))
	  ((> COL *SCREEN-COLS*))
	  (POP LST) )
	(INCQ ROW) ))
    (DECQ MAX) ) )

(DEFUN SHOW-OPTION (NUM OPTIONS
    ROW COL)
  ((NOT NUM))
  (SETQ ROW 0)
  (LOOP
    (SETQ COL *OPTION-COLUMN*)
    (LOOP
      ((ZEROP NUM)
	(SET-CURSOR ROW COL)
	(WRITE-STRING (SUBSTRING (CAAR OPTIONS) 0 (SUB1 *MAX-LENGTH*)))
	(RETURN) )
      (SETQ COL (+ COL (MIN *MAX-LENGTH* (LENGTH (CAAR OPTIONS)))))
      (DECQ NUM)
      (POP OPTIONS)
      ((>= (+ COL (MIN *MAX-LENGTH* (LENGTH (CAAR OPTIONS)))) *SCREEN-COLS*))
      (INCQ COL) )
    (INCQ ROW) ) )

(DEFUN MODE-QUERY (TITLE OPTIONS
    NUM COLUMN QUERY ROWS COLS)
  (OPTION-WINDOW)
  (CLEAR-SCREEN)
  (WRITE-STRING TITLE)
  (WRITE-STRING ": ")
  (SETQ COLUMN (IF (SMALL-SCREENP) 2 (COLUMN))
	NUM 0)
  (LOOP
    ((= NUM (LENGTH OPTIONS)))
    (SETQ QUERY (NTH NUM OPTIONS))
    (IF (> (+ (COLUMN) (LENGTH (THIRD QUERY)) 2 (QUERY-LENGTH (FOURTH QUERY)))
	   *SCREEN-COLS*)
	(SET-CURSOR (ADD1 (ROW)) COLUMN) )
    (IF (ZEROP (COLUMN))
	(SET-CURSOR (ROW) COLUMN) )
    (WRITE-STRING (THIRD QUERY))
    (IF (AND (NEQ (THIRD QUERY) "")
	     (EQ (THIRD QUERY) (STRING-RIGHT-TRIM " " (THIRD QUERY))))
	(WRITE-STRING ": "))
    (PUSH (ROW) ROWS)
    (PUSH (COLUMN) COLS)
    (IF (INTEGERP (FOURTH QUERY))
	(WRITE-STRING (SUBSTRING (MAKE-STRING (CAR QUERY)) 0
				 (SUB1 (FOURTH QUERY))))
	(SHOW-MODES (CAR QUERY) (FOURTH QUERY)) )
    (SET-CURSOR (ROW) (+ (CAR COLS) (QUERY-LENGTH (FOURTH QUERY)) 1))
    (INCQ NUM) )
  (SETQ ROWS (NREVERSE ROWS)
	COLS (NREVERSE COLS)
	NUM 0)
  (LOOP
    (SETQ QUERY (NTH NUM OPTIONS))
    (RPLACA QUERY (APPLY 'MAKE-QUERY (NTH NUM ROWS) (NTH NUM COLS) QUERY))
    ((MEMBER *LINE-TERMINATOR* *EDIT-TERMINATORS*)
      (NEQ *LINE-TERMINATOR* 27) )
    ((AND (ZEROP *LINE-TERMINATOR*) (EQ (LENGTH OPTIONS) 1)))
    ( ((OR (EQ *LINE-TERMINATOR* 9) (ZEROP *LINE-TERMINATOR*))
	(SETQ NUM (MOD (ADD1 NUM) (LENGTH OPTIONS))) )
      ((OR (EQ *LINE-TERMINATOR* 2) (EQ *LINE-TERMINATOR* -15))
	(SETQ NUM (MOD (SUB1 NUM) (LENGTH OPTIONS))) ) ) ) )

(DEFUN MAKE-QUERY (ROW COLUMN DEFAULT PROMPT TITLE OPTIONS
    POSITION NUM )
  (SHOW-PROMPT PROMPT)
  ((INTEGERP OPTIONS)
    (OPTION-WINDOW)
    (SET-CURSOR ROW COLUMN)
    (SETQ NUM (CSMEMORY 914 0 T))			; Disable tabbing
    (PROG1 (LINE-EDITOR DEFAULT '(27 13 10 9 2 -15) 0 0 OPTIONS)
	   (CSMEMORY 914 NUM T) ) )			; Enable tabbing
  (SETQ NUM (POSITION DEFAULT OPTIONS))
  (LOOP
    (OPTION-WINDOW)
    (SET-CURSOR ROW (SUB1 COLUMN))
    (SPACES 1)
    (SETQ *LINE-TERMINATOR* (SELECT-OPTION NUM OPTIONS))
    ((MEMBER *LINE-TERMINATOR* '(27 13 10 9 2 -15)))
    ((OR (SETQ POSITION (POSITION (CHAR-UPCASE (ASCII *LINE-TERMINATOR*))
				OPTIONS 'CHAR=))
	 (AND (ALPHA-CHAR-P (ASCII *LINE-TERMINATOR*))
	      (SETQ POSITION (POSITION (CHAR-UPCASE (ASCII *LINE-TERMINATOR*))
				     OPTIONS 'FINDSTRING))))
      (SETQ NUM POSITION
	    *LINE-TERMINATOR* 0) )
    ( ((= *LINE-TERMINATOR* 32)
	(SETQ NUM (MOD (ADD1 NUM) (LENGTH OPTIONS))) )
      ((= *LINE-TERMINATOR* 8)
	(SETQ NUM (MOD (SUB1 NUM) (LENGTH OPTIONS))) )
      (ERROR-BEEP) ) )
  (SETQ DEFAULT (NTH NUM OPTIONS))
  (OPTION-WINDOW)
  (SET-CURSOR ROW COLUMN)
  (SHOW-MODES DEFAULT OPTIONS)
  DEFAULT )

(DEFUN SHOW-MODES (DEFAULT OPTIONS
    NUM)
  (SETQ NUM 0)
  (LOOP
    ((ATOM OPTIONS))
    ( ((EQUAL DEFAULT (CAR OPTIONS))
	(WRITE-BYTE 8)
	(WRITE-STRING "(")
	(WRITE-STRING (POP OPTIONS))
	(WRITE-STRING ")") )
      (WRITE-STRING (POP OPTIONS))
      (SPACES 1) )
    (INCQ NUM) ) )

(DEFUN SELECT-OPTION (DEFAULT OPTIONS
    MODE NUM)
  (SETQ NUM 0)
  (LOOP
    ((ATOM OPTIONS))
    (SETQ MODE (POP OPTIONS))
    ( ((EQ NUM DEFAULT)
	(CHANGE-COLOR *MENU-BACKGROUND* *OPTION-COLOR* 0)
	(WRITE-STRING MODE)
	(CHANGE-COLOR *OPTION-COLOR* *MENU-BACKGROUND*) )
      (WRITE-STRING MODE) )
    ( ((= (COLUMN) 0))
      (SPACES 1) )
    (INCQ NUM) )
  (PROMPT-WINDOW)
  (LOOP
    ((READ-CONSOLE-STATUS)) ) )

(DEFUN QUERY-LENGTH (OPTIONS
    NUM)
  ((INTEGERP OPTIONS)
    (ADD1 OPTIONS) )
  (SETQ NUM 0)
  (LOOP
    ((ATOM OPTIONS) NUM)
    (SETQ NUM (+ NUM (LENGTH (POP OPTIONS)) 1)) ) )

(DEFUN RESTORE-BORDER ()
  ((ZEROP (WINDOW-ROW 0))
    (WINDOW-ROW 0 1)
    (WINDOW-COL 0 1)
    (WINDOW-ROWS 0 (SUB1 (WINDOW-ROWS 0)))
    (WINDOW-COLS 0 (- (WINDOW-COLS 0) 2)) ) )

(DEFUN BORDER-WINDOWS (
    WINDOW ROW1 COL1 ROW2 COL2)
  (SETQ *CURRENT-AREA*)
  (MAKE-WINDOW NIL)
  (CHANGE-COLOR *FRAME-COLOR* *MENU-BACKGROUND*)
  ((ZEROP (WINDOW-ROW 0))
    ((MEDIUM-RESOLUTION-P))
    (HORIZONTAL-BORDER (WINDOW-ROWS 0) 0 *SCREEN-COLS*) )
  (HORIZONTAL-BORDER 0 1 (- *SCREEN-COLS* 2))
  (VERTICAL-BORDER 1 0 (- *SCREEN-ROWS* 6))
  (SETQ WINDOW 0)
  (LOOP
    ((= WINDOW (LENGTH *WINDOWS*)))
    (SETQ ROW1 (SUB1 (WINDOW-ROW WINDOW))
	  COL1 (SUB1 (WINDOW-COL WINDOW))
	  ROW2 (+ (WINDOW-ROW WINDOW) (WINDOW-ROWS WINDOW))
	  COL2 (+ (WINDOW-COL WINDOW) (WINDOW-COLS WINDOW)))
    (SET-CURSOR ROW1 COL1)
    ( ((= WINDOW *CURRENT-WINDOW*)
	(CHANGE-COLOR *MENU-BACKGROUND* *FRAME-COLOR* 0)
	(PRIN1 (ADD1 WINDOW))
	(CHANGE-COLOR *FRAME-COLOR* *MENU-BACKGROUND*) )
      (PRIN1 (ADD1 WINDOW)) )
    (SET-CURSOR ROW1 COL2)
    ( ((UPPER-LEFT ROW1 COL2))
      ((LOWER-RIGHT ROW1 COL2)
	(WRITE-BORDER 9) )
      (WRITE-BORDER 2) )
    (SET-CURSOR ROW2 COL1)
    ( ((UPPER-LEFT ROW2 COL1))
      ((LOWER-RIGHT ROW2 COL1)
	(WRITE-BORDER 6) )
      (WRITE-BORDER 4) )
    (SETQ ROW1 (ADD1 ROW1)
	  COL1 (ADD1 COL1))
    ( ((AND (= ROW2 (- *SCREEN-ROWS* 5)) (MEDIUM-RESOLUTION-P)))
      (HORIZONTAL-BORDER ROW2 COL1 (- COL2 COL1)) )
    (VERTICAL-BORDER ROW1 COL2 (- ROW2 ROW1))
    (INCQ WINDOW) )
  ((MEDIUM-RESOLUTION-P))
  (SET-CURSOR ROW2 COL2)
  (WRITE-BORDER 5) )

(DEFUN HORIZONTAL-BORDER (ROW COL COLS)
  (SET-CURSOR ROW COL)
  (WRITE-BORDER 0 COLS) )

(DEFUN VERTICAL-BORDER (ROW COL ROWS)
  (SETQ ROWS (+ ROW ROWS))
  (LOOP
    ((>= ROW ROWS))
    (SET-CURSOR ROW COL)
    (WRITE-BORDER 7)
    (INCQ ROW) ) )

(DEFUN WRITE-BORDER (CHAR NUM)
  (WRITE-BYTE (NTH CHAR *BORDER-CHARS*) NUM) )

(DEFUN CURRENT-WINDOW (FLAG)
  (CHANGE-COLOR (CAR (WORK-COLOR)) (CAR (WORK-BACKGROUND)))
  ( ((EQUAL *CURRENT-AREA*
	    (SETQ *CURRENT-AREA* (CDDR (NTH *CURRENT-WINDOW* *WINDOWS*)))))
    (MAKE-WINDOW (WINDOW-ROW) (WINDOW-COL) (WINDOW-ROWS) (WINDOW-COLS)) )
  ((NOT FLAG))
  (CLEAR-SCREEN) )

(DEFUN OPTION-WINDOW (
    ROWS)
  (CHANGE-COLOR *OPTION-COLOR* *MENU-BACKGROUND*)
  (SETQ *OPTIONS*)
  ((EQ *CURRENT-AREA* (SETQ *CURRENT-AREA* 'OPTION-WINDOW)))
  (SETQ ROWS (IF (SMALL-SCREENP) 3 2))
  (MAKE-WINDOW (- *SCREEN-ROWS* ROWS 2) 0 ROWS *SCREEN-COLS*) )

(DEFUN PROMPT-WINDOW ()
  ((EQ *CURRENT-AREA* (SETQ *CURRENT-AREA* 'PROMPT-WINDOW)))
  (CHANGE-COLOR *PROMPT-COLOR* *MENU-BACKGROUND*)
  (MAKE-WINDOW (- *SCREEN-ROWS* 2) 0 1 *SCREEN-COLS*) )

(DEFUN STATUS-WINDOW ()
  ((EQ *CURRENT-AREA* (SETQ *CURRENT-AREA* 'STATUS-WINDOW)))
  (CHANGE-COLOR *STATUS-COLOR* *MENU-BACKGROUND*)
  (MAKE-WINDOW (SUB1 *SCREEN-ROWS*) 0 1 *SCREEN-COLS*) )

(DEFUN CONTINUE-PROMPT (
    BYTE)
  (CLEAR-INPUT T)
  (LOOP
    (SETQ BYTE (PROMPT-READ-BYTE "Press any key to continue"))
    ((NEQ BYTE 19) BYTE) ) )

(DEFUN PROMPT-YN (PROMPT
    BYTE )
  (LOOP
    (SETQ BYTE (PROMPT-READ-BYTE PROMPT))
    ((MEMBER BYTE '(89 121 25))
      (WRITE-BYTE 89 NIL T)
      (SETQ *PROMPT*)
      T )
    ((MEMBER BYTE '(78 110 14))
      (WRITE-BYTE 78 NIL T)
      (SETQ *PROMPT*) )
    (ERROR-BEEP) ) )

(DEFUN PROMPT-READ-BYTE (PROMPT)
  (PROMPT-WINDOW)
  ( ((EQ PROMPT *PROMPT*)
      (SET-CURSOR 0 (LENGTH *PROMPT*)) )
    (CLEAR-SCREEN)
    (SETQ *PROMPT* (WRITE-STRING PROMPT T)) )
  (READ-CONSOLE-BYTE) )

(DEFUN ERROR-MESSAGE (PROMPT)
  (SHOW-PROMPT PROMPT)
  (SETQ *PROMPT* "Enter option")
  (ERROR-BEEP) )

(DEFUN SHOW-PROMPT (PROMPT)
  ((OR (NULL PROMPT) (EQ PROMPT *PROMPT*)))
  (PROMPT-WINDOW)
  (CLEAR-SCREEN)
  (SETQ *PROMPT* (WRITE-STRING PROMPT T))
  (SET-CURSOR 0 0) )

(DEFUN ERROR-BEEP ()
  ((EQ *MUTE* "Yes"))
  (CLEAR-INPUT)
  ((EQ (CSMEMORY 855) 2)
    (TONE 784 25)
    (TONE 698 50) )
  (WRITE-BYTE 7) )

(DEFUN MAKE-STRING (EXPN)
  ((SYMBOLP EXPN) EXPN)
  (PACK* EXPN) )

(IF (EQ *DEFAULT-TYPE* '*DEFAULT-TYPE*) (SETQ *DEFAULT-TYPE* ""))

(DEFUN PROMPT-TEXT-FILE (COMMAND FILE-NAME)
  (SETQ FILE-NAME (STRING-UPCASE
		(PROMPT-INPUT "Enter file name" COMMAND FILE-NAME)))
  ((OR (EQ *LINE-TERMINATOR* 27) (EQ FILE-NAME "")) "")
  (NORMALIZE-FILE-NAME FILE-NAME *DEFAULT-TYPE*) )

(DEFUN NORMALIZE-FILE-NAME (FILE-NAME DEFAULT-TYPE
    NUM)
  (SETQ NUM (IF (EQ (CHAR FILE-NAME 1) '\:) 2 0))
  ( ((EQ (CHAR FILE-NAME NUM) '\.)
      (INCQ NUM)
      ((EQ (CHAR FILE-NAME NUM) '\.)
	(INCQ NUM) ) ) )
  ((SETQ NUM (FINDSTRING '\. FILE-NAME NUM))
    (SUBSTRING FILE-NAME 0 (+ NUM 3)) )
  (PACK* FILE-NAME '\. DEFAULT-TYPE) )

(DEFUN PROMPT-INPUT (PROMPT COMMAND DEFAULT)
  (SHOW-PROMPT PROMPT)
  (OPTION-WINDOW)
  (CLEAR-SCREEN)
  (WRITE-STRING COMMAND T)
  (LINE-EDITOR DEFAULT *EDIT-TERMINATORS* 0 0 (- *SCREEN-COLS* (COLUMN) 1)) )

(DEFUN LINE-EDITOR (STRING TERMINATORS *LINE-POINT* *LINE-COLUMN* COLS
    ROW COL )
  (SETQ ROW (ROW)
	COL (COLUMN))
  (LOOP
    (OPTION-WINDOW)
    (SET-CURSOR ROW COL)
    (CURSOR-ON)
    (SETQ STRING (LINE-EDIT STRING *LINE-POINT* *LINE-COLUMN* COLS))
    (CURSOR-OFF)
    ((MEMBER *LINE-TERMINATOR* TERMINATORS)
      (STRING-TRIM " " STRING) )
    ( ((MEMBER *LINE-TERMINATOR* '(11 15)))
      (DEMON-BYTE *LINE-TERMINATOR*) ) ) )


(SETQ *FREE-STATUS* NIL)	; If nonNIL, function called after GC's.

(DEFUN GCHOOK (
    ROW COL FOREGROUND-COLOR BACKGROUND-COLOR WINDOW
    *CURRENT-AREA* *OUTPUT-FILE*)
  ( ((ZEROP (SETQ *FREE-DATA* (DSMEMORY 8 NIL T)))
      (SETQ *FREE-DATA* 65536) ) )
  (SETQ *FREE-DATA* (TRUNCATE (* 100 (MIN
	    (/ (- (+ (- *FREE-DATA* (DSMEMORY 6 NIL T)) (DSMEMORY 2 NIL T))
		  (DSMEMORY 0 NIL T))
	       *FREE-DATA*)
	    (/ (- (DSMEMORY 44 NIL T) (DSMEMORY 46 NIL T))
	       (- 65536 (DSMEMORY 46 NIL T)))
	    (/ (- (DSMEMORY 42 NIL T) (DSMEMORY 40 NIL T))
	       (DSMEMORY 42 NIL T))))))
  ((NOT *FREE-STATUS*))
  (SETQ ROW (ROW)
	COL (COLUMN)
	FOREGROUND-COLOR (FOREGROUND-COLOR)
	BACKGROUND-COLOR (BACKGROUND-COLOR)
	WINDOW (MAKE-WINDOW))
  (FUNCALL *FREE-STATUS*)
  (APPLY 'MAKE-WINDOW WINDOW)
  (FOREGROUND-COLOR FOREGROUND-COLOR)
  (BACKGROUND-COLOR BACKGROUND-COLOR)
  (SET-CURSOR ROW COL) )


(DEFUN CLEAR-STATUS (PROMPT)
  (STATUS-WINDOW)
  (CLEAR-SCREEN)
  (INSERT-STATUS *INSERT-MODE*)
  (SET-CURSOR 0 (- *SCREEN-COLS* (LENGTH PROMPT)))
  (WRITE-STRING PROMPT T)
  (SET-CURSOR 0 0)
  ((SMALL-SCREENP))
  (SET-CURSOR 0 (- (- *SCREEN-COLS* (LENGTH PROMPT)) (ADD1 (LENGTH *PRODUCT*))))
  (WRITE-STRING *PRODUCT* T)
  (SET-CURSOR 0 0) )

(DEFUN SMALL-SCREENP ()
  (< *SCREEN-COLS* 75) )


(DEFUN PARSE-INTEGER-CAR (STRING)
  (PARSE-INTEGER (CAR STRING)) )

(DEFUN PARSE-INTEGER (STRING RADIX
    CHAR SIGN N )
  (SETQ *STRING-INDEX* 0)
  (LOOP
    ((NULL (SETQ CHAR (CHAR STRING *STRING-INDEX*))) NIL)
    ((NEQ CHAR '| |)
      (SETQ SIGN 1)
      ( ((EQ CHAR '+)
	  (INCQ *STRING-INDEX*) )
	((EQ CHAR '-)
	  (SETQ SIGN -1)
	  (INCQ *STRING-INDEX*) ) )
      ((SETQ CHAR (CHAR STRING *STRING-INDEX*))
	((SETQ N (DIGIT-CHAR-P CHAR RADIX))
	  (IF (NULL RADIX) (SETQ RADIX 10))
	  (LOOP
	    (INCQ *STRING-INDEX*)
	    ((NULL (SETQ CHAR (CHAR STRING *STRING-INDEX*))))
	    ((NOT (SETQ CHAR (DIGIT-CHAR-P CHAR RADIX))))
	    (SETQ N (+ (* N RADIX) CHAR)) )
	  (* SIGN N) ) ) )
    (INCQ *STRING-INDEX*) ) )

(DEFUN READ-CONSOLE-STATUS (
    *INPUT-FILE*)
  (LOOP
    (IF *UPDATE-FUNCTION* (FUNCALL *UPDATE-FUNCTION*))
    ((NOT (LISTEN)) NIL)
    ((DEMON-BYTE (READ-CONSOLE-BYTE))) ) )

(DEFUN READ-CONSOLE-BYTE (
    *INPUT-FILE*)
  (CURSOR-ON)
  (PROG1 (CONSOLE-BYTE (READ-BYTE))
	 (CURSOR-OFF)) )

(DEFUN DEMON-BYTE (BYTE
    DEMON)
  (SETQ BYTE (NORMALIZE-BYTE BYTE))
  ((SETQ DEMON (OR (ASSOC BYTE *LOCAL-DEMONS*) (ASSOC BYTE *GLOBAL-DEMONS*)))
    (FUNCALL (CDR DEMON) BYTE)
    (IF *UPDATE-FUNCTION* (FUNCALL *UPDATE-FUNCTION*))
    NIL )
  BYTE )

(DEFUN NORMALIZE-BYTE (BYTE)
  ( ((<= -103 BYTE -94) 		;Ctrl Fx --> Shift Fx
      (SETQ BYTE (+ BYTE 10)) )
    ((<= -113 BYTE -104)		;Alt Fx --> Shift Fx
      (SETQ BYTE (+ BYTE 20)) ) )
  ((CDR (ASSOC BYTE *CURSOR-KEYS*)))
  BYTE )

(SETQ *CURSOR-KEYS* '(
	(-72 . 5)			;Up arrow	Ctrl-E
	(-80 . 24)			;Down arrow	Ctrl-X
	(-75 . 19)			;<--		Ctrl-S
	(-77 . 4)			;-->		Ctrl-D
	(-73 . 18)			;PgUp		Ctrl-R
	(-81 . 3)			;PgDn		Ctrl-C
	(-115 . 1)			;Ctrl <--	Ctrl-A
	(-116 . 6)			;Ctrl -->	Ctrl-F
	(-82 . 22)			;Ins		Ctrl-V
	(-83 . 7) ))			;Del		Ctrl-G

(SETQ *GLOBAL-DEMONS* '(
	(22 . TOGGLE-INSERT)		;Ctrl-V (Ins)
	(-59 . NEXT-WINDOW)		;F1
	(-84 . LAST-WINDOW)		;Shift F1
	(-60 . NEXT-PANE)		;F2
	(-85 . LAST-PANE) ))		;Shift F2

;	* * *	Computer customization section	 * * *

(SETQ *BORDER-CHARS* '(45 32 32 45 32 32 45 124 124 124 43))  ;Generic values

(MOVD 'IDENTITY 'SAVE-STATE)		;Save external state
(MOVD 'IDENTITY 'RESTORE-STATE) 	;Restore external state
(MOVD 'IDENTITY 'INITIAL-ENTRY) 	;Initial entry routine
(MOVD 'IDENTITY 'CHANGE-COLOR)		;Set foreground and background colors
(MOVD 'WRITE-STRING 'BLINK-WRITE-STRING)
(MOVD 'IDENTITY 'CURSOR-ON)
(MOVD 'IDENTITY 'CURSOR-OFF)
(MOVD 'IDENTITY 'CONSOLE-BYTE)

(DEFUN WRITE-CONSOLE (BYTE)
  (REGISTER 0 512)
  (REGISTER 3 BYTE)
  (INTERRUPT 33) )

(IF (EQ (CSMEMORY 855) 2)			;IBM PC?
    (PROGN

(SETQ *BORDER-CHARS* '(205 213 184 209 212 190 207 179 198 181 216))

(DEFUN SAVE-STATE ()
; Save external video state as the list *EXTERNAL-STATE*.
  (SETQ *EXTERNAL-STATE*
	(LIST (FOREGROUND-COLOR) (BACKGROUND-COLOR)
	      (VIDEO-MODE) (BORDER-COLOR))) )

(DEFUN RESTORE-STATE (
; Restores external video state and returns NIL if video mode is not changed.
    *VIDEO-MODE* *BORDER-COLOR*)
  (FOREGROUND-COLOR (FIRST *EXTERNAL-STATE*))
  (BACKGROUND-COLOR (SECOND *EXTERNAL-STATE*))
  (SET-VIDEO-MODE (THIRD *EXTERNAL-STATE*) (FOURTH *EXTERNAL-STATE*) T) )

(DEFUN CHANGE-COLOR (FOREGROUND-COLOR BACKGROUND-COLOR FLAG
; Sets the foreground and background color based on 16 logical colors.
; FLAG is nonNIL if for inverse video.
    MODE)
  ((SETQ MODE (VIDEO-MODE))
    ( ((OR (= MODE 7) (= MODE 15) (= MODE 17))		; 3 colors?
	((= FOREGROUND-COLOR BACKGROUND-COLOR)
	  (SETQ FOREGROUND-COLOR 0
		BACKGROUND-COLOR 0) )
	((NOT FLAG)
	  ((ZEROP BACKGROUND-COLOR)			; Normal video?
	    (SETQ FOREGROUND-COLOR (IF (<= FOREGROUND-COLOR 7) 7 15)) )
	  (SETQ FOREGROUND-COLOR 0			; Inverse video?
		BACKGROUND-COLOR 7) )
	((ZEROP FOREGROUND-COLOR)			; Inverse video?
	  (SETQ BACKGROUND-COLOR 7) )
	(SETQ FOREGROUND-COLOR (IF (<= BACKGROUND-COLOR 7) 7 15)
	      BACKGROUND-COLOR 0) )
      ((GRAPHICS-MODE-P)				; Graphics mode?
	((= FOREGROUND-COLOR BACKGROUND-COLOR))
	((OR (= MODE 6) (= MODE 64) (<= 126 MODE 127))	; 2 colors?
	  ((= (LOGAND FOREGROUND-COLOR 1) (LOGAND BACKGROUND-COLOR 1))
	    (IF FLAG (INCQ BACKGROUND-COLOR) (INCQ FOREGROUND-COLOR)) ) )
	((OR (<= 4 MODE 5) (= MODE 10)) 		; 4 colors?
	  ((= (LOGAND FOREGROUND-COLOR 3) (LOGAND BACKGROUND-COLOR 3))
	    (IF FLAG (INCQ BACKGROUND-COLOR) (INCQ FOREGROUND-COLOR)) ) ) )
      ((= FOREGROUND-COLOR BACKGROUND-COLOR)
	(SETQ BACKGROUND-COLOR (LOGAND BACKGROUND-COLOR 7)
	      FOREGROUND-COLOR BACKGROUND-COLOR) )
      (SETQ BACKGROUND-COLOR (LOGAND BACKGROUND-COLOR 7)); Prevents blinking
      ((= FOREGROUND-COLOR BACKGROUND-COLOR)
	(IF FLAG (INCQ BACKGROUND-COLOR) (INCQ FOREGROUND-COLOR))
	(SETQ BACKGROUND-COLOR (LOGAND BACKGROUND-COLOR 7)) ) )
    (IF (= MODE 17) (SETQ BACKGROUND-COLOR (LOGAND BACKGROUND-COLOR 1)))
    (FOREGROUND-COLOR FOREGROUND-COLOR)
    (BACKGROUND-COLOR BACKGROUND-COLOR) ) )

(DEFUN BLINK-WRITE-STRING (STRING
    NUM1 NUM2 MODE)
  (SETQ NUM1 (FOREGROUND-COLOR)
	NUM2 (BACKGROUND-COLOR)
	MODE (VIDEO-MODE))
  ( ((EQ MODE 7)
      (BACKGROUND-COLOR 15) )			;Turn on blinking
    ((EQ MODE 15)
      (FOREGROUND-COLOR 4)
      (BACKGROUND-COLOR 0) )			;Turn on blinking
    ((GRAPHICS-MODE-P)
      (FOREGROUND-COLOR NUM2)
      (BACKGROUND-COLOR NUM1) ) 		;Turn on inverse video
    (BACKGROUND-COLOR (LOGIOR 8 NUM2)) )
  (WRITE-STRING STRING) 			;Write string
  (FOREGROUND-COLOR NUM1)
  (BACKGROUND-COLOR NUM2) )

(DEFUN CURSOR-ON (				;Turn cursor ON
    LST)
  (CURSOR-LINES NIL)
  ((NOT *INSERT-MODE*))
  ((SETQ LST (CURSOR-LINES))
    (CURSOR-LINES (- (CAR LST) 2) (CADR LST)) ) )

(DEFUN CURSOR-OFF ()				;Turn cursor OFF
  ((NOT *CURSOR-ON*)
    (CURSOR-LINES 14 0) ) )

(DEFUN CONSOLE-BYTE (BYTE)
  ((AND (= BYTE 255) (LISTEN))			;Extended function key?
    (- (READ-BYTE)) )
  BYTE )
))


(IF (<= 9 (CSMEMORY 855) 10)			;NEC PC-9801 or Fujitsu?
    (PROGN

(SETQ *BORDER-CHARS* '(149 152 153 145 154 155 144 150 147 146 143))

(DEFUN WRITE-BORDER (CHAR NUM)
  (MAPC 'WRITE-CONSOLE '(27 41 51))		;Activate graphics mode
  (WRITE-BYTE (NTH CHAR *BORDER-CHARS*) NUM)
  (MAPC 'WRITE-CONSOLE '(27 41 48)) )		;Activate kanji mode

(DEFUN RESTORE-STATE () 			;Restore external video state
  (CURSOR-ON)
  NIL )

(DEFUN CURSOR-ON ()				;Turn cursor ON
  (MAPC 'WRITE-CONSOLE '(27 91 62 53 108)) )

(DEFUN CURSOR-OFF ()				;Turn cursor OFF
  ((NOT *CURSOR-ON*)
    (MAPC 'WRITE-CONSOLE '(27 91 62 53 104)) ) )

(DEFUN CONSOLE-BYTE (BYTE)
  ((AND (EQ BYTE 27) (LISTEN))			;Function key?
    (SETQ BYTE (READ-BYTE))
    ((CDR (ASSOC BYTE '(
	(83 . -59)				;F1
	(84 . -60)				;F2
	(85 . -61)				;F3
	(86 . -62)				;F4
	(87 . -63)				;F5
	(69 . -64)				;F6
	(74 . -65)				;F7
;	(80 . -66)				;F8
	(81 . -67)				;F9
	(68 . -83)				;Del
	(80 . -82) )))) 			;Ins
    (UNREAD-CHAR)
    27 )
  ((EQ BYTE 127) -68)				;F10
  BYTE )
))


(IF (OR (<= 3 (CSMEMORY 855) 4) 		;ANSI or TI-PC?
	(<= 8 (CSMEMORY 855) 10))		;NEC XA, 9801 or Fujitsu?
    (PROGN

(DEFUN CHANGE-COLOR (FOREGROUND-COLOR BACKGROUND-COLOR)
  ((ZEROP (LOGAND BACKGROUND-COLOR 7))
    (MAPC 'WRITE-CONSOLE '(27 91 48 109)) )	;Normal video
  (MAPC 'WRITE-CONSOLE '(27 91 48 59 55 109)) ) ;Inverse video

(DEFUN BLINK-WRITE-STRING (STRING)
  (MAPC 'WRITE-CONSOLE '(27 91 48 59 53 109))	;Turn blink mode ON
  (WRITE-STRING STRING) 			;Write string
  (MAPC 'WRITE-CONSOLE '(27 91 48 109)) )	;Turn blink mode OFF
))


(IF (EQ (CSMEMORY 855) 5) (PROGN		;Z-100?

(SETQ *BORDER-CHARS* '(97 102 99 117 101 100 117 96 118 116 98))

(DEFUN SAVE-STATE ()				;Disable key expansion
  (MAPC 'WRITE-CONSOLE '(27 122 27 121 63)) )

(DEFUN RESTORE-STATE () 			;Enable key expansion
  (CURSOR-ON)
  (MAPC 'WRITE-CONSOLE '(27 122))
  NIL )

(DEFUN WRITE-BORDER (CHAR NUM)
  (MAPC 'WRITE-CONSOLE '(27 70))		;Activate graphics mode
  (WRITE-BYTE (NTH CHAR *BORDER-CHARS*) NUM)
  (MAPC 'WRITE-CONSOLE '(27 71)) )		;Deactivate graphics mode

(DEFUN CHANGE-COLOR (FOREGROUND-COLOR BACKGROUND-COLOR)
  ((ZEROP (LOGAND BACKGROUND-COLOR 7))
    (MAPC 'WRITE-CONSOLE '(27 113)) )		;Normal video
  (MAPC 'WRITE-CONSOLE '(27 112)) )		;Inverse video

(DEFUN BLINK-WRITE-STRING (STRING)
  (MAPC 'WRITE-CONSOLE '(27 112))		;Turn reverse video ON
  (WRITE-STRING STRING) 			;Write string
  (MAPC 'WRITE-CONSOLE '(27 113)) )		;Turn reverse video OFF

(DEFUN CURSOR-ON ()				;Turn cursor ON
  (MAPC 'WRITE-CONSOLE '(27 121 53)) )

(DEFUN CURSOR-OFF ()				;Turn cursor OFF
  ((NOT *CURSOR-ON*)
    (MAPC 'WRITE-CONSOLE '(27 120 53)) ) )

(SETQ *CURSOR-KEYS* '(		;Z-100 Key	      Generic Key
	(165 . 5)		;Up arrow		Ctrl-E
	(184 . 5)		;Keypad 5		Ctrl-E
	(166 . 24)		;Down arrow		Ctrl-X
	(178 . 24)		;Keypad 2		Ctrl-X
	(168 . 19)		;<--			Ctrl-S
	(180 . 19)		;Keypad 4		Ctrl-S
	(167 . 4)		;-->			Ctrl-D
	(182 . 4)		;Keypad 6		Ctrl-D
	(185 . 18)		;Keypad 9		Ctrl-R
	(249 . 18)		;Shift-Keypad 9 	Ctrl-R
	(179 . 3)		;Keypad 3		Ctrl-C
	(243 . 3)		;Shift-Keypad 3 	Ctrl-C
	(244 . 1)		;Shift-Keypad 4 	Ctrl-A
	(246 . 6)		;Shift-Keypad 6 	Ctrl-F
	(176 . 22)		;Keypad 0		Ctrl-V
	(240 . 22)		;Shift-Keypad 0 	Ctrl-V
	(174 . 7)		;Keypad .		Ctrl-G
	(238 . 7)		;Shift-Keypad . 	Ctrl-G
	(227 . 7)		;D CHR			Ctrl-G

	(163 . 22)		;I CHR			Ctrl-V
	(151 . -59)		;F1			F1
	(215 . -84)		;Shift F1		Shift F1
	(152 . -60)		;F2			F2
	(216 . -85)		;Shift F2		Shift F2
	(228 . 25)		;DELLINE		Ctrl-Y
	(164 . 14)		;INSLINE		Ctrl-N
	(232 . -31)		;Shift <--		Alt-S
	(167 . -32)		;Shift -->		Alt-D
	(229 . -19)		;Shift Up arrow 	Alt-R
	(230 . -46)		;Shift Down arrow	Alt-C
	(173 . -20)		;Keypad -		Alt-T
	(237 . -20)		;Shift-Keypad - 	Alt-T
	(169 . -71)		;HOME			Home
	(183 . -71)		;Keypad 7		Home
	(247 . -119)		;Shift-Keypad 7 	Ctrl-Home
	(233 . -79)		;Shift-HOME		End
	(177 . -79)		;Keypad 1		End
	(241 . -117)		;Shift-Keypad 1 	Ctrl-End
	(141 . -120)		;ENTER			Alt-!
	(205 . -120) )) ))	;Shift-ENTER		Alt-!
